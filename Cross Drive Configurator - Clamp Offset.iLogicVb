Sub Main()

    Dim oRawDoc As Document = ThisApplication.ActiveDocument

    If oRawDoc.DocumentType <> DocumentTypeEnum.kAssemblyDocumentObject Then
        MessageBox.Show("Run this rule in an assembly.", "iLogic")
        Exit Sub
    End If

    Dim oAsm As AssemblyDocument = CType(oRawDoc, AssemblyDocument)
    Dim oDef As AssemblyComponentDefinition = oAsm.ComponentDefinition
    Dim oParams As Parameters = oDef.Parameters

    Try

        ' Clamp Offset
        If oParams.Item("A1").Value = oParams.Item("B1").Value Then

            oParams.Item("Clamp_Offset1").Value = _
                ((oParams.Item("C12").Value - oParams.Item("D6").Value) + _
                (oParams.Item("D6").Value / 2)) - _
                (oParams.Item("C13").Value + oParams.Item("CC").Value)

        ElseIf oParams.Item("Shoe_Count1").Value > oParams.Item("Shoe_Count2").Value Then

            oParams.Item("Clamp_Offset1").Value = _
                ((oParams.Item("D6").Value / 2) + oParams.Item("SC").Value) - _
                (oParams.Item("C13").Value + oParams.Item("CC").Value)

        ElseIf oParams.Item("Shoe_Count1").Value < oParams.Item("Shoe_Count2").Value Then

            oParams.Item("Clamp_Offset1").Value = _
                ((oParams.Item("C12").Value - oParams.Item("D6").Value) + _
                (oParams.Item("D6").Value / 2)) - _
                (oParams.Item("C13").Value + oParams.Item("CC").Value + oParams.Item("SC").Value)

        End If

        oAsm.Update2()

    Catch ex As Exception
        MessageBox.Show("Clamp Offset rule failed: " & ex.Message, "Error")
    End Try

End Sub
