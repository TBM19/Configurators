Sub Main()

    Const CONTROLS_TITLE As String = "CONTROLS"
    Const RUN_GUARD As String = "Controls_Model_State_Rule_Running"

    If SharedVariable.Exists(RUN_GUARD) Then Exit Sub

    SharedVariable(RUN_GUARD) = True

    Try

        If ThisDoc.Document.DocumentType <> _
            DocumentTypeEnum.kAssemblyDocumentObject Then Exit Sub

        Dim controlsOccName As String = ""
        Dim targetState As String = ""

        '------------------------------------------------
        ' READ REQUIRED PARAMETERS
        '------------------------------------------------
        Dim ShoeStyle As String = ""
        Dim ValveMountStyle As String = ""

        Try
            ShoeStyle = CStr(Parameter("Shoe_Style"))
        Catch
            Exit Sub
        End Try

        Try
            ValveMountStyle = CStr(Parameter("Valve_Mount_Style"))
        Catch
            Exit Sub
        End Try

        ShoeStyle = Trim(ShoeStyle)
        ValveMountStyle = Trim(ValveMountStyle)

        '------------------------------------------------
        ' DETERMINE TARGET MODEL STATE
        '
        ' AVAILABLE MODEL STATES:
        '   End Mount 5.0 inch CC
        '   End Mount 10.0 inch CC
        '   Mid Mount 5.0 inch CC
        '   Mid Mount 10.0 inch CC
        '------------------------------------------------
        If String.Equals( _
            ValveMountStyle, _
            "Mid Mount", _
            StringComparison.OrdinalIgnoreCase) Then

            If String.Equals( _
                ShoeStyle, _
                "Wide Shoe 16 Hole (WS16H)", _
                StringComparison.OrdinalIgnoreCase) Then

                targetState = "Mid Mount 10.0 inch CC"

            Else

                targetState = "Mid Mount 5.0 inch CC"

            End If

        ElseIf String.Equals( _
            ValveMountStyle, _
            "End Mount", _
            StringComparison.OrdinalIgnoreCase) Then

            If String.Equals( _
                ShoeStyle, _
                "Wide Shoe 16 Hole (WS16H)", _
                StringComparison.OrdinalIgnoreCase) Then

                targetState = "End Mount 10.0 inch CC"

            Else

                targetState = "End Mount 5.0 inch CC"

            End If

        Else

            MessageBox.Show( _
                "The Valve_Mount_Style parameter contains an " & _
                "unsupported value:" & vbCrLf & vbCrLf & _
                "'" & ValveMountStyle & "'" & vbCrLf & vbCrLf & _
                "The supported values are:" & vbCrLf & _
                "Mid Mount" & vbCrLf & _
                "End Mount", _
                "Invalid Valve Mount Style")

            Exit Sub

        End If

        Dim oAsm As AssemblyDocument = _
            CType(ThisDoc.Document, AssemblyDocument)

        '------------------------------------------------
        ' FIND FIRST CONTROLS ANYWHERE
        '------------------------------------------------
        FindFirstControls( _
            oAsm.ComponentDefinition.Occurrences, _
            controlsOccName, _
            CONTROLS_TITLE)

        If controlsOccName = "" Then Exit Sub

        '------------------------------------------------
        ' READ CURRENT MODEL STATE
        '------------------------------------------------
        Dim currentState As String = ""

        Try

            currentState = _
                Component.ActiveModelState(controlsOccName)

        Catch

            Exit Sub

        End Try

        '------------------------------------------------
        ' ALREADY CORRECT
        '------------------------------------------------
        If String.Equals( _
            Trim(currentState), _
            Trim(targetState), _
            StringComparison.OrdinalIgnoreCase) Then

            Exit Sub

        End If

        '------------------------------------------------
        ' CHANGE MODEL STATE
        '------------------------------------------------
        Try

            Component.ActiveModelState(controlsOccName) = _
                targetState

            InventorVb.DocumentUpdate()

        Catch ex As Exception

            MessageBox.Show( _
                "Controls occurrence found:" & vbCrLf & _
                controlsOccName & vbCrLf & vbCrLf & _
                "Valve mount style:" & vbCrLf & _
                ValveMountStyle & vbCrLf & vbCrLf & _
                "Shoe style:" & vbCrLf & _
                ShoeStyle & vbCrLf & vbCrLf & _
                "Model state '" & targetState & _
                "' could not be applied." & vbCrLf & vbCrLf & _
                ex.Message, _
                "Model State Error")

        End Try

    Finally

        If SharedVariable.Exists(RUN_GUARD) Then
            SharedVariable.Remove(RUN_GUARD)
        End If

    End Try

End Sub


'====================================================
' FIND FIRST CONTROLS
'====================================================
Private Sub FindFirstControls( _
    ByVal occs As ComponentOccurrences, _
    ByRef controlsOccName As String, _
    ByVal controlsTitle As String)

    For Each occ As ComponentOccurrence In occs

        If controlsOccName <> "" Then Exit Sub

        Try

            If occ.Suppressed Then Continue For

            If String.Equals( _
                Trim(GetTitle(occ)), _
                Trim(controlsTitle), _
                StringComparison.OrdinalIgnoreCase) Then

                controlsOccName = occ.Name

                Exit Sub

            End If

            If occ.SubOccurrences.Count > 0 Then

                FindFirstControls( _
                    occ.SubOccurrences, _
                    controlsOccName, _
                    controlsTitle)

            End If

        Catch
        End Try

    Next

End Sub


'====================================================
' GET TITLE
'====================================================
Private Function GetTitle( _
    ByVal occ As ComponentOccurrence) As String

    Try

        Return CStr( _
            occ.Definition.Document.PropertySets( _
            "Inventor Summary Information") _
            .Item("Title").Value)

    Catch

        Return ""

    End Try

End Function
